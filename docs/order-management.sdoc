[DOCUMENT]
TITLE: Order Management — 機能・振る舞い・シナリオ

[REQUIREMENT]
UID: ORD-FEAT-001
TAGS: FEATURE
TITLE: Order
STATEMENT: 注文の作成とキャンセルを管理する。

[REQUIREMENT]
UID: ORD-FEAT-002
TAGS: FEATURE
TITLE: Create Order
STATEMENT: 注文を作成する機能。今回のPoCでは振る舞い・実装の対象外。
RELATIONS:
- TYPE: Parent
  VALUE: ORD-FEAT-001

[REQUIREMENT]
UID: ORD-FEAT-003
TAGS: FEATURE
TITLE: Cancel Order
STATEMENT: 注文の出荷状態に応じてキャンセルを受け付けるか判断する。
RELATIONS:
- TYPE: Parent
  VALUE: ORD-FEAT-001

[REQUIREMENT]
UID: ORD-BEH-001
TAGS: BEHAVIOR
TITLE: 出荷前の注文はキャンセルできる
STATEMENT: 出荷前の注文はキャンセルできる。決済済みの場合はキャンセル時に返金済み状態へ遷移する。キャンセル済み注文への再要求は拒否する。
RELATIONS:
- TYPE: Parent
  VALUE: ORD-FEAT-003

[REQUIREMENT]
UID: ORD-SCN-001
TAGS: SCENARIO
TITLE: 未決済注文をキャンセル
STATEMENT: 未決済・未出荷の注文をキャンセルすると、キャンセル成功となり返金は発生しない。
RELATIONS:
- TYPE: Parent
  VALUE: ORD-BEH-001

[REQUIREMENT]
UID: ORD-SCN-002
TAGS: SCENARIO
TITLE: 決済済み注文をキャンセルして返金
STATEMENT: 決済済み・未出荷の注文をキャンセルすると、キャンセル成功となり返金済み状態になる。
RELATIONS:
- TYPE: Parent
  VALUE: ORD-BEH-001

[REQUIREMENT]
UID: ORD-SCN-004
TAGS: SCENARIO
TITLE: キャンセル済み注文を再度キャンセルできない
STATEMENT: キャンセル済み注文を再度キャンセルすると拒否され、注文状態は変化しない。
RELATIONS:
- TYPE: Parent
  VALUE: ORD-BEH-001

[REQUIREMENT]
UID: ORD-BEH-002
TAGS: BEHAVIOR
TITLE: 出荷後の注文はキャンセルできない
STATEMENT: 出荷済みの注文のキャンセル要求は拒否し、注文状態を変更しない。
RELATIONS:
- TYPE: Parent
  VALUE: ORD-FEAT-003

[REQUIREMENT]
UID: ORD-SCN-003
TAGS: SCENARIO
TITLE: shipped=true の注文を拒否
STATEMENT: shipped=true の注文をキャンセルすると失敗し、キャンセル・返金状態は変更されない。
RELATIONS:
- TYPE: Parent
  VALUE: ORD-BEH-002
